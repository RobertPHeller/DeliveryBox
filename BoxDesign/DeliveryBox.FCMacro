#*****************************************************************************
#
#  System        : 
#  Module        : 
#  Object Name   : $RCSfile$
#  Revision      : $Revision$
#  Date          : $Date$
#  Author        : $Author$
#  Created By    : Robert Heller
#  Created       : 2026-06-16 16:40:27
#  Last Modified : <260710.1320>
#
#  Description	
#
#  Notes
#
#  History
#	
#*****************************************************************************
#
#    Copyright (C) 2026  Robert Heller D/B/A Deepwoods Software
#			51 Locke Hill Road
#			Wendell, MA 01379-9728
#
#    This program is free software; you can redistribute it and/or modify
#    it under the terms of the GNU General Public License as published by
#    the Free Software Foundation; either version 2 of the License, or
#    (at your option) any later version.
#
#    This program is distributed in the hope that it will be useful,
#    but WITHOUT ANY WARRANTY; without even the implied warranty of
#    MERCHANTABILITY or FITNESS FOR A PARTICULAR PURPOSE.  See the
#    GNU General Public License for more details.
#
#    You should have received a copy of the GNU General Public License
#    along with this program; if not, write to the Free Software
#    Foundation, Inc., 675 Mass Ave, Cambridge, MA 02139, USA.
#
# 
#
#*****************************************************************************


import FreeCAD as App
import Part, TechDraw, Mesh
from FreeCAD import Base

import os
import sys
sys.path.append(os.path.dirname(__file__))
import Units
from debug import debug
import datetime                                                                 
from PianoHinge import *

import time

import csv 

from PySide.QtCore import QCoreApplication, QEventLoop, QTimer

def execute(loop, ms):
    timer = QTimer()
    timer.setSingleShot(True)
    
    timer.timeout.connect(loop.quit)
    timer.start(ms)
    loop.exec_()

def sleep(ms):
    if not QCoreApplication.instance():
        app = QCoreApplication([])
        execute(app, ms)
    else:
        loop = QEventLoop()
        execute(loop, ms)
                                        


def NormalizeMM(x):
    return round(x,3)

class BOMHelper(object):
    __BOM = dict()
    @classmethod
    def AddPiece(cls,width,height,kind):
        key = (NormalizeMM(width),NormalizeMM(height),kind)
        if key in cls.__BOM:
            cls.__BOM[key] += 1
        else:
            cls.__BOM[key] = 1
    @classmethod
    def _normPartSizeMM(cls,t):
        return ("%.3fx%.3f" % t)
    @staticmethod
    def _inch(mm):
        return mm / 25.4
    @classmethod
    def _normPartSizeIN(cls,t):
        X, Y = t
        return ("%.4fx%.4f" % (cls._inch(X), cls._inch(Y)))
    _units = 'in'
    @classmethod
    def SetUnits(cls,units):
        if units == 'in' or units == 'mm':
            cls._units = units
        else:
            raise RuntimeError("Unsupport units!")
    @classmethod
    def GetUnits(cls):
        return cls._units
    @classmethod
    def _normPartSize(cls,t):
        if cls._units == 'in':
            return cls._normPartSizeIN(t)
        elif cls._units == 'mm':
            return BOMHelper._normPartSizeMM(t)
        else:
            raise RuntimeError("Unsupport units!")
    @classmethod
    def ListCuts(cls,filename):
        keys = list(cls.__BOM.keys())
        keys.sort()
        f = open(filename,"w")
        w = csv.writer(f)
        w.writerow([("Size (%s)" % cls._units),"Count"])
        for key in keys:
            X, Y, kind = key
            w.writerow([cls._normPartSize((X,Y)),kind,cls.__BOM[key]])
        f.close()
    

class Sheet(BOMHelper):
    def __init__(self):
        raise RuntimeError("No Instances allowed for Sheet")
    __CDX3_8Thick = Units.mm(11/32)
    @classmethod
    def CDXThick(cls):
        return cls.__CDX3_8Thick
    __Color = (1.0,1.0,0.0)
    @classmethod
    def Color(cls):
        return cls.__Color
    @classmethod
    def XYSheet(cls,origin,width,length,sheettype="CDX"):
        if not isinstance(origin,Base.Vector):
            raise RuntimeError("origin is not a Vector!")
        thick = None
        kind = None
        if sheettype == "CDX":
            thick = cls.__CDX3_8Thick
            kind = "3/8 CDX Plywood"
        else:
            raise RuntimeError("Unsupport plywood type")
        sheet = Part.makePlane(width,length,origin,Base.Vector(0,0,1)).extrude(Base.Vector(0,0,thick))
        bb = sheet.BoundBox
        cls.AddPiece(bb.XLength,bb.YLength,kind)
        return sheet
    @classmethod
    def XZSheet(cls,origin,width,length,sheettype="CDX"):
        if not isinstance(origin,Base.Vector):
            raise RuntimeError("origin is not a Vector!")
        thick = None
        kind = None
        if sheettype == "CDX":
            thick = cls.__CDX3_8Thick
            kind = "3/8 CDX Plywood"
        else:
            raise RuntimeError("Unsupport plywood type")
        sheet = Part.makePlane(width,length,origin,Base.Vector(0,1,0)).extrude(Base.Vector(0,thick,0))
        bb = sheet.BoundBox
        cls.AddPiece(bb.XLength,bb.ZLength,kind)
        return sheet
    @classmethod
    def YZSheet(cls,origin,width,length,sheettype="CDX"):
        if not isinstance(origin,Base.Vector):
            raise RuntimeError("origin is not a Vector!")
        thick = None
        kind = None
        if sheettype == "CDX":
            thick = cls.__CDX3_8Thick
            kind = "3/8 CDX Plywood"
        else:
            raise RuntimeError("Unsupport plywood type")
        sheet = Part.makePlane(width,length,origin.add(Base.Vector(0,length,0)),Base.Vector(1,0,0)).extrude(Base.Vector(thick,0,0))
        bb = sheet.BoundBox
        cls.AddPiece(bb.ZLength,bb.YLength,kind)
        return sheet
    
class SpruceDimStock(BOMHelper):
    def __init__(self):
        raise RuntimeError("No Instances allowed for SpruceDimStock!") 
    __thick = Units.mm(1.5)
    @classmethod
    def BoardThickness(cls):
        return cls.__thick
    __x4Width = Units.mm(3.5)
    @classmethod
    def X4Width(cls):
        return cls.__x4Width    
    __x6Width = Units.mm(5.5)
    @classmethod
    def X6Width(cls):
        return cls.__x6Width    
    __Color = (0xBA/255.0, 0x70/255.0, 0x0F/255.0)
    @classmethod
    def Color(cls):
        return cls.__Color
    @classmethod
    def ZXBoard(cls,origin,width,length):
        if not isinstance(origin,Base.Vector):
            raise RuntimeError("origin is not a Vector!")
        board = Part.makePlane(width,length,origin,Base.Vector(0,1,0)).extrude(Base.Vector(0,cls.__thick,0))
        bb = board.BoundBox
        cls.AddPiece(bb.ZLength,bb.XLength,"2in Dimensional Stock")
        return board
    @classmethod
    def YXBoard(cls,origin,width,length):
        if not isinstance(origin,Base.Vector):
            raise RuntimeError("origin is not a Vector!")
        board = Part.makePlane(width,length,origin,Base.Vector(0,0,1)).extrude(Base.Vector(0,0,cls.__thick))
        bb = board.BoundBox
        cls.AddPiece(bb.YLength,bb.XLength,"2in Dimensional Stock")
        return board
    @classmethod
    def ZYBoard(cls,origin,width,length):
        if not isinstance(origin,Base.Vector):
            raise RuntimeError("origin is not a Vector!")
        board = Part.makePlane(width,length,origin.add(Base.Vector(0,length,0)),
                               Base.Vector(1,0,0)) \
                  .extrude(Base.Vector(cls.__thick,0,0))
        bb = board.BoundBox
        cls.AddPiece(bb.ZLength,bb.YLength,"2in Dimensional Stock")
        return board
    @classmethod
    def XYBoard(cls,origin,width,length):
        if not isinstance(origin,Base.Vector):
            raise RuntimeError("origin is not a Vector!")
        board = Part.makePlane(width,length,origin,Base.Vector(0,0,1)).extrude(Base.Vector(0,0,cls.__thick))
        bb = board.BoundBox
        cls.AddPiece(bb.YLength,bb.XLength,"2in Dimensional Stock")
        return board
    @classmethod
    def ZBeam(cls,origin,length):
        if not isinstance(origin,Base.Vector):
            raise RuntimeError("origin is not a Vector!")
        beam = Part.makePlane(cls.__thick,cls.__thick,origin,Base.Vector(0,0,1)).extrude(Base.Vector(0,0,length))
        bb = beam.BoundBox
        cls.AddPiece(bb.YLength,bb.ZLength,"2in Dimensional Stock")
        return beam
    @classmethod
    def XBeam(cls,origin,length):
        if not isinstance(origin,Base.Vector):
            raise RuntimeError("origin is not a Vector!")
        beam = Part.makePlane(cls.__thick,cls.__thick,origin,Base.Vector(1,0,0)).extrude(Base.Vector(length,0,0))
        bb = beam.BoundBox
        cls.AddPiece(bb.YLength,bb.XLength,"2in Dimensional Stock")
        return beam
    @classmethod
    def YBeam(cls,origin,length):
        if not isinstance(origin,Base.Vector):
            raise RuntimeError("origin is not a Vector!")
        beam = Part.makePlane(cls.__thick,cls.__thick,origin,Base.Vector(0,1,0)).extrude(Base.Vector(0,length,0))
        bb = beam.BoundBox
        cls.AddPiece(bb.XLength,bb.YLength,"2in Dimensional Stock")
        return beam

    
## Chewy box: 24x17x6

class Wheel(object):
    __Diameter = Units.mm(6)
    __Width    = Units.mm(1.5)
    __Bore     = Units.mm(5/8)
    __Color    = (0.0,0.0,0.0)
    @classmethod
    def Width(cls):
        return cls.__Width
    @classmethod
    def Diameter(cls):
        return cls.__Diameter
    @classmethod
    def Bore(cls):
        return cls.__Bore
    def __init__(self,name,origin,orient=Base.Vector(1,0,0)):
        if not isinstance(origin,Base.Vector):
            raise RuntimeError("origin is not a Vector!")
        self.origin = origin
        self.name = name
        self.wheel = Part.makeCylinder(self.__Diameter/2.0,self.__Width,origin,orient)
        self.wheel = self.wheel.cut(Part.makeCylinder(self.__Bore/2.0,self.__Width,origin,orient))
    def show(self,doc=None):
        if doc==None:
            doc = App.activeDocument()
        obj = doc.addObject("Part::Feature",self.name)
        obj.Shape = self.wheel
        obj.Label=self.name
        obj.ViewObject.ShapeColor=self.__Color
        
class DeliveryBox(object):
    __OuterWidth = Units.mm(20)
    __OuterLength = Units.mm(24)
    __OuterHeight = Units.mm(30)
    __LegLength = Units.mm(3)
    @property
    def OuterLength(self):
        return self.__OuterLength
    @property
    def OuterWidth(self):
        return self.__OuterWidth
    @property
    def OuterHeight(self):
        return self.__OuterHeight
    @property
    def LegLength(self):
        return self.__LegLength
    def _XZFrame(self,origin,height,width,addlegs=False):
        if addlegs:
            a = SpruceDimStock.ZBeam(origin.add(Base.Vector(0,0,
                                                            -self.LegLength)),
                                     height+self.LegLength)
        else:
            a = SpruceDimStock.ZBeam(origin,height)
        b = SpruceDimStock.XBeam(origin.add(
                                   Base.Vector(SpruceDimStock.BoardThickness(),
                                               SpruceDimStock.BoardThickness(),
                                               0)),
                                 width-(2*SpruceDimStock.BoardThickness()))
        if addlegs:
            c = SpruceDimStock.ZBeam(origin.add(
                                    Base.Vector(width-
                                        SpruceDimStock.BoardThickness(),0,
                                        -self.LegLength)),
                                  height+self.LegLength)
        else:
            c = SpruceDimStock.ZBeam(origin.add(
                                    Base.Vector(width-
                                        SpruceDimStock.BoardThickness(),0,0)),
                                  height)
        d = SpruceDimStock.XBeam(origin.add(
                                   Base.Vector(SpruceDimStock.BoardThickness(),
                                               SpruceDimStock.BoardThickness(),
                                               height-SpruceDimStock.BoardThickness())),
                                 width-(2*SpruceDimStock.BoardThickness()))
        return (a, b, c, d)
    def _XYFrame(self,origin,width,length):
        a = SpruceDimStock.YBeam(origin,length);
        b = SpruceDimStock.XBeam(origin.add(
                                   Base.Vector(SpruceDimStock.BoardThickness(),
                                               SpruceDimStock.BoardThickness(),0)),
                                 width-(2*SpruceDimStock.BoardThickness()))
        c = SpruceDimStock.YBeam(origin.add(
                                    Base.Vector(width-SpruceDimStock.BoardThickness(),
                                                0,0)),length);
        d = SpruceDimStock.XBeam(origin.add(
                                   Base.Vector(SpruceDimStock.BoardThickness(),
                                               length,0)),
                                 width-(2*SpruceDimStock.BoardThickness()))
        return (a, b, c, d)
    def __init__(self,name,origin):
        ## Wood parts (3/8 CDX and 2" dim stock (2x2 and 2x4))
        if not isinstance(origin,Base.Vector):
            raise RuntimeError("origin is not a Vector!")
        self.origin = origin
        self.name = name
        self.left_side = Sheet.YZSheet(self.origin,self.OuterHeight,
                                       self.OuterLength)
        self.right_side = Sheet.YZSheet(self.origin.add(
                                            Base.Vector(self.OuterWidth-
                                                        Sheet.CDXThick(),0,0)),
                                        self.OuterHeight,
                                        self.OuterLength)
        self.front_side = Sheet.XZSheet(self.origin.add(
                                            Base.Vector(Sheet.CDXThick(),0,0)),
                                        self.OuterHeight,
                                        self.OuterWidth-(2*Sheet.CDXThick()))
        self.front_frame  = self._XZFrame(self.origin.add(
                                        Base.Vector(Sheet.CDXThick(),
                                                    Sheet.CDXThick(),0)),
                                   self.OuterHeight,
                                   self.OuterWidth-(2*Sheet.CDXThick()))
        self.rear_side = Sheet.XZSheet(self.origin.add(
                                          Base.Vector(Sheet.CDXThick(),
                                                      self.OuterLength-
                                                          Sheet.CDXThick(),0)),
                                        self.OuterHeight,
                                        self.OuterWidth-(2*Sheet.CDXThick()))
        self.rear_frame = self._XZFrame(self.origin.add(
                                        Base.Vector(Sheet.CDXThick(),
                                                    self.OuterLength-
                                                        Sheet.CDXThick()-
                                                        SpruceDimStock.BoardThickness(),0)),
                                   self.OuterHeight,
                                   self.OuterWidth-(2*Sheet.CDXThick()),True)
        self.left_bottom_ybeam = SpruceDimStock.YBeam(origin.add(Base.Vector(
                                                    Sheet.CDXThick(),
                                                    Sheet.CDXThick()+
                                                    SpruceDimStock.BoardThickness(),
                                                    0)),
                                                    self.OuterLength-(2*(
                                                        Sheet.CDXThick()+
                                                        SpruceDimStock.BoardThickness())))
        self.left_top_ybeam = SpruceDimStock.YBeam(origin.add(Base.Vector(
                                                    Sheet.CDXThick(),
                                                    Sheet.CDXThick()+
                                                    SpruceDimStock.BoardThickness(),
                                                    self.OuterHeight-
                                                        SpruceDimStock.BoardThickness())),
                                                    self.OuterLength-(2*(
                                                        Sheet.CDXThick()+
                                                        SpruceDimStock.BoardThickness())))
        self.right_bottom_ybeam = SpruceDimStock.YBeam(origin.add(Base.Vector(
                                                    self.OuterWidth-Sheet.CDXThick()-SpruceDimStock.BoardThickness(),
                                                    Sheet.CDXThick()+
                                                    SpruceDimStock.BoardThickness(),
                                                    0)),
                                                    self.OuterLength-(2*(
                                                        Sheet.CDXThick()+
                                                        SpruceDimStock.BoardThickness())))
        self.right_top_ybeam = SpruceDimStock.YBeam(origin.add(Base.Vector(
                                                    self.OuterWidth-Sheet.CDXThick()-SpruceDimStock.BoardThickness(),
                                                    Sheet.CDXThick()+
                                                    SpruceDimStock.BoardThickness(),
                                                    self.OuterHeight-
                                                        SpruceDimStock.BoardThickness())),
                                                    self.OuterLength-(2*(
                                                        Sheet.CDXThick()+
                                                        SpruceDimStock.BoardThickness())))
        self.bottom = Sheet.XYSheet(origin.add(Base.Vector(0,0,
                                                           -Sheet.CDXThick())),
                                    self.OuterWidth,
                                    self.OuterLength)
        self.bottom = self.bottom.cut(
            self.rear_frame[0]).cut(
            self.rear_frame[2])
        self.lid_frame = self._XYFrame(origin.add(
                                        Base.Vector(0,0,self.OuterHeight)),
                                       self.OuterWidth,
                                       self.OuterLength)
        self.lid = Sheet.XYSheet(origin.add(
                                  Base.Vector(0,0,self.OuterHeight+
                                             SpruceDimStock.BoardThickness())),
                                 self.OuterWidth,
                                 self.OuterLength)
        self.lid_lockboard = SpruceDimStock.XYBoard(
                            origin.add(
                               Base.Vector((self.OuterWidth/2)-
                                               (SpruceDimStock.X4Width()/2),
                                            SpruceDimStock.BoardThickness(),
                                            self.OuterHeight)),
                            SpruceDimStock.X4Width(),
                            self.OuterLength-
                                           (2*SpruceDimStock.BoardThickness()))
        ## Hardware: wheels, lock, handle, hinge, etc.
        self.hinge = PianoHingeFlatOutsideBack(self.name+"_hinge",
                                               origin.add(
                        Base.Vector((self.OuterWidth-
                                        PianoHingeFlatOutsideBack.Length())/2,
                                    self.OuterLength,
                                    self.OuterHeight-
                                       PianoHingeFlatOutsideBack.FlangeWidth()-
                                       (PianoHingeFlatOutsideBack.PinDia()/2))))
        self.leftWheel = Wheel(self.name+"_leftWheel",origin.add(
                         Base.Vector(-Wheel.Width(),Wheel.Diameter()/2,-Wheel.Bore())))
        self.rightWheel = Wheel(self.name+"_rightWheel",origin.add(
                         Base.Vector(self.OuterWidth,Wheel.Diameter()/2,-Wheel.Bore())))
        self.axle = Part.makeCylinder(Wheel.Bore()/2,
                                      self.OuterWidth+2*Wheel.Width()+Units.mm(1),
                                      origin.add(Base.Vector(-(Wheel.Width()+Units.mm(1/2)),
                                                             Wheel.Diameter()/2,
                                                             -Wheel.Bore())),
                                      Base.Vector(1,0,0))
    def show(self,doc=None):
        if doc==None:
            doc = App.activeDocument()
        obj = doc.addObject("Part::Feature",self.name+"_left_side")
        obj.Shape = self.left_side
        obj.Label=self.name+"_left_side"
        obj.ViewObject.ShapeColor=Sheet.Color()        
        obj = doc.addObject("Part::Feature",self.name+"_right_side")
        obj.Shape = self.right_side
        obj.Label=self.name+"_right_side"
        obj.ViewObject.ShapeColor=Sheet.Color()        
        obj = doc.addObject("Part::Feature",self.name+"_front_side")
        obj.Shape = self.front_side
        obj.Label=self.name+"_front_side"
        obj.ViewObject.ShapeColor=Sheet.Color()        
        obj = doc.addObject("Part::Feature",self.name+"_rear_side")
        obj.Shape = self.rear_side
        obj.Label=self.name+"_rear_side"
        obj.ViewObject.ShapeColor=Sheet.Color()        
        a, b, c, d = self.front_frame
        obj = doc.addObject("Part::Feature",self.name+"_front_frame_a")
        obj.Shape = a
        obj.Label=self.name+"_front_frame_a"
        obj.ViewObject.ShapeColor=SpruceDimStock.Color()
        obj = doc.addObject("Part::Feature",self.name+"_front_frame_b")
        obj.Shape = b
        obj.Label=self.name+"_front_frame_b"
        obj.ViewObject.ShapeColor=SpruceDimStock.Color()
        obj = doc.addObject("Part::Feature",self.name+"_front_frame_c")
        obj.Shape = c
        obj.Label=self.name+"_front_frame_c"
        obj.ViewObject.ShapeColor=SpruceDimStock.Color()
        obj = doc.addObject("Part::Feature",self.name+"_front_frame_d")
        obj.Shape = d
        obj.Label=self.name+"_front_frame_d"
        obj.ViewObject.ShapeColor=SpruceDimStock.Color()
        a, b, c, d = self.rear_frame
        obj = doc.addObject("Part::Feature",self.name+"_rear_frame_a")
        obj.Shape = a
        obj.Label=self.name+"_rear_frame_a"
        obj.ViewObject.ShapeColor=SpruceDimStock.Color()
        obj = doc.addObject("Part::Feature",self.name+"_rear_frame_b")
        obj.Shape = b
        obj.Label=self.name+"_rear_frame_b"
        obj.ViewObject.ShapeColor=SpruceDimStock.Color()
        obj = doc.addObject("Part::Feature",self.name+"_rear_frame_c")
        obj.Shape = c
        obj.Label=self.name+"_rear_frame_c"
        obj.ViewObject.ShapeColor=SpruceDimStock.Color()
        obj = doc.addObject("Part::Feature",self.name+"_rear_frame_d")
        obj.Shape = d
        obj.Label=self.name+"_rear_frame_d"
        obj.ViewObject.ShapeColor=SpruceDimStock.Color()
        obj = doc.addObject("Part::Feature",self.name+"_left_bottom_ybeam")
        obj.Shape = self.left_bottom_ybeam
        obj.Label=self.name+"_left_bottom_ybeam"
        obj.ViewObject.ShapeColor=SpruceDimStock.Color()
        obj = doc.addObject("Part::Feature",self.name+"_left_top_ybeam")
        obj.Shape = self.left_top_ybeam
        obj.Label=self.name+"_left_top_ybeam"
        obj.ViewObject.ShapeColor=SpruceDimStock.Color()
        obj = doc.addObject("Part::Feature",self.name+"_right_bottom_ybeam")
        obj.Shape = self.right_bottom_ybeam
        obj.Label=self.name+"_right_bottom_ybeam"
        obj.ViewObject.ShapeColor=SpruceDimStock.Color()
        obj = doc.addObject("Part::Feature",self.name+"_right_top_ybeam")
        obj.Shape = self.right_top_ybeam
        obj.Label=self.name+"_right_top_ybeam"
        obj.ViewObject.ShapeColor=SpruceDimStock.Color()
        obj = doc.addObject("Part::Feature",self.name+"_bottom")
        obj.Shape = self.bottom
        obj.Label=self.name+"_bottom"
        obj.ViewObject.ShapeColor=Sheet.Color()        
        a, b, c, d = self.lid_frame
        obj = doc.addObject("Part::Feature",self.name+"_lid_frame_a")
        obj.Shape = a
        obj.Label=self.name+"_lid_frame_a"
        obj.ViewObject.ShapeColor=SpruceDimStock.Color()
        obj = doc.addObject("Part::Feature",self.name+"_lid_frame_b")
        obj.Shape = b
        obj.Label=self.name+"_lid_frame_b"
        obj.ViewObject.ShapeColor=SpruceDimStock.Color()
        obj = doc.addObject("Part::Feature",self.name+"_lid_frame_c")
        obj.Shape = c
        obj.Label=self.name+"_lid_frame_c"
        obj.ViewObject.ShapeColor=SpruceDimStock.Color()
        obj = doc.addObject("Part::Feature",self.name+"_lid_frame_d")
        obj.Shape = d
        obj.Label=self.name+"_lid_frame_d"
        obj.ViewObject.ShapeColor=SpruceDimStock.Color()
        obj = doc.addObject("Part::Feature",self.name+"_lid")
        obj.Shape = self.lid
        obj.Label=self.name+"_lid"
        obj.ViewObject.ShapeColor=Sheet.Color()        
        obj = doc.addObject("Part::Feature",self.name+"_lid_lockboard")
        obj.Shape = self.lid_lockboard
        obj.Label=self.name+"_lid_lockboard"
        obj.ViewObject.ShapeColor=SpruceDimStock.Color()
        self.hinge.show(doc)
        self.leftWheel.show(doc)
        self.rightWheel.show(doc)
        obj = doc.addObject("Part::Feature",self.name+"_axle")
        obj.Shape = self.axle
        obj.Label=self.name+"_axle"
        obj.ViewObject.ShapeColor=(0.9,0.9,0.9)
        
if __name__ == '__main__':
    if "BenchWork" in App.listDocuments().keys():
        App.closeDocument("DeliveryBox")
    doc = App.newDocument("DeliveryBox")
    doc = App.activeDocument()
    deliveryBox = DeliveryBox("DeliveryBox",Base.Vector(0,0,0))
    deliveryBox.show(doc)
    Gui.activeDocument().activeView().viewRear()
    Gui.SendMsgToActiveView("ViewFit")
    BOMHelper.ListCuts("BOM.csv")
